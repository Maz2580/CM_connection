FME workspace calling_python_to_download.fmw

Parameters:
- SourceDataset_XLSXR = E:\Administration\Projects\SP 2048 Automating content manger data for renewal programs\custom_search\download_test\M24_116779.XLSX   # Source Microsoft Excel File(s)
- SourceDataset_XLSXR_25 = E:\Administration\Projects\SP 2048 Automating content manger data for renewal programs\custom_search\download_test\M25_29906.XLSX   # Source Microsoft Excel File(s)
- SourceDataset_XLSXR_19 = E:\Administration\Projects\SP 2048 Automating content manger data for renewal programs\custom_search\download_test\M25_68009.XLSX   # Source Microsoft Excel File(s)
- SourceDataset_XLSXR_23 = E:\Administration\Projects\SP 2048 Automating content manger data for renewal programs\custom_search\download_test\M25_71471.XLSX   # Source Microsoft Excel File(s)
- SourceDataset_XLSXR_27 = E:\Administration\Projects\SP 2048 Automating content manger data for renewal programs\custom_search\download_test\M25_90558.XLSX   # Source Microsoft Excel File(s)
- SourceDataset_XLSXR_16 = E:\Administration\Projects\SP 2048 Automating content manger data for renewal programs\custom_search\download_test\M25_103918.XLSX   # Source Microsoft Excel File(s)
- SourceDataset_XLSXR_18 = E:\Administration\Projects\SP 2048 Automating content manger data for renewal programs\custom_search\download_test\M24_122925.XLSX   # Source Microsoft Excel File(s)
- SourceDataset_XLSXR_20 = E:\Administration\Projects\SP 2048 Automating content manger data for renewal programs\custom_search\download_test\M24_122925.XLSX   # Source Microsoft Excel File(s)
- SourceDataset_XLSXR_17 = E:\Administration\Projects\SP 2048 Automating content manger data for renewal programs\custom_search\download_test\M25_36103.XLSX   # Source Microsoft Excel File(s)
- SourceDataset_XLSXR_21 = E:\Administration\Projects\SP 2048 Automating content manger data for renewal programs\custom_search\download_test\M25_41564.XLSX   # Source Microsoft Excel File(s)
- SourceDataset_XLSXR_15 = E:\Administration\Projects\SP 2048 Automating content manger data for renewal programs\custom_search\download_test\M25_68009.XLSX   # Source Microsoft Excel File(s)
- SourceDataset_XLSXR_22 = E:\Administration\Projects\SP 2048 Automating content manger data for renewal programs\custom_search\download_test\M25_71471.XLSX   # Source Microsoft Excel File(s)
- SourceDataset_XLSXR_24 = E:\Administration\Projects\SP 2048 Automating content manger data for renewal programs\custom_search\download_test\M25_90558.XLSX   # Source Microsoft Excel File(s)
- SourceDataset_XLSXR_26 = E:\Administration\Projects\SP 2048 Automating content manger data for renewal programs\custom_search\download_test\M25_103918.XLSX   # Source Microsoft Excel File(s)

Readers:
- XLSXR_1: XLSXR from $(SourceDataset_XLSXR)
- XLSXR_3: XLSXR from $(SourceDataset_XLSXR_25)
- XLSXR_6: XLSXR from $(SourceDataset_XLSXR_19)
- XLSXR_7: XLSXR from $(SourceDataset_XLSXR_23)
- XLSXR_8: XLSXR from $(SourceDataset_XLSXR_27)
- XLSXR_9: XLSXR from $(SourceDataset_XLSXR_16)
- XLSXR_10: XLSXR from $(SourceDataset_XLSXR_18)
- XLSXR_11: XLSXR from $(SourceDataset_XLSXR_20)
- XLSXR_2: XLSXR from $(SourceDataset_XLSXR_17)
- XLSXR_4: XLSXR from $(SourceDataset_XLSXR_21)
- XLSXR_5: XLSXR from $(SourceDataset_XLSXR_15)
- XLSXR_12: XLSXR from $(SourceDataset_XLSXR_22)
- XLSXR_13: XLSXR from $(SourceDataset_XLSXR_24)
- XLSXR_14: XLSXR from $(SourceDataset_XLSXR_26)

Note: make sure to set the download_config if you are adding any new data / its located at the "E:\Administration\Projects\SP 2048 Automating content manger data for renewal programs\custom_search\download_config.json"

Bookmark: Downloading and filtering excel files
PythonCreator_2
    NEW_ATTRIBUTES = record_number char(200) title char(200) filename char(200) filepath char(200) source_record char(200) download_timestamp char(200) success logical total_files int32 downloaded_count int32 failed_count int32 error_message char(200) download_status char(200)
    PYTHONSOURCE_NEW:
      import fmeobjects
      import subprocess
      import os
      import json


      class FeatureCreator:
          """
          PythonCreator: Downloads files from Content Manager and creates
          one feature per downloaded file.
          """

          def __init__(self):
              # Use UNC path for network accessibility: \\vm46\gis$ (mapped as E:)
              self.script_dir = r"E:\Administration\Projects\SP 2048 Automating content manger data for renewal programs\custom_search"
              self.python_exe = os.path.join(self.script_dir, "venv32", "Scripts", "python.exe")
              self.batch_script = os.path.join(self.script_dir, "batch_download.py")
              self.config_file = os.path.join(self.script_dir, "download_config.json")

              # Logger
              self.logger = fmeobjects.FMELogFile()

              # Store features to output
              self.features_to_output = []

          def log(self, message, severity=fmeobjects.FME_INFORM):
              """Log message to FME"""
              self.logger.logMessageString(str(message), severity)

          def input(self, feature):
              """
              Called for each input feature.
              In PythonCreator, this is called once with a dummy feature.
              We do all our work here and store features in a list.
              """

              self.log("=" * 60)
              self.log("Starting Content Manager Download...")
              self.log("=" * 60)

              # Run the batch download script
              try:
                  result = subprocess.run(
                      [self.python_exe, self.batch_script],
                      capture_output=True,
                      text=True,
                      cwd=self.script_dir,
                      timeout=300
                  )

                  if result.stdout:
                      for line in result.stdout.strip().split('\n'):
                          self.log(line)

                  if result.stderr:
                      self.log(f"STDERR: {result.stderr}", fmeobjects.FME_WARN)

                  self.log(f"Download script exit code: {result.returncode}")

              except Exception as e:
                  self.log(f"ERROR: {e}", fmeobjects.FME_ERROR)
                  self.features_to_output.append(self._create_error_feature(str(e)))
                  return

              # Read config
              try:
                  with open(self.config_file, 'r') as f:
                      config = json.load(f)
                  output_dir = config.get("output_directory", "")
              except Exception as e:
                  self.log(f"Config error: {e}", fmeobjects.FME_ERROR)
                  self.features_to_output.append(self._create_error_feature(f"Config error: {e}"))
                  return

              # Read manifest
              manifest_path = os.path.join(output_dir, "manifest.json")

              if not os.path.exists(manifest_path):
                  self.log(f"Manifest not found: {manifest_path}", fmeobjects.FME_ERROR)
                  self.features_to_output.append(self._create_error_feature("Manifest not created"))
                  return

              try:
                  with open(manifest_path, 'r') as f:
                      manifest = json.load(f)
              except Exception as e:
                  self.log(f"Manifest error: {e}", fmeobjects.FME_ERROR)
                  self.features_to_output.append(self._create_error_feature(f"Manifest error: {e}"))
                  return

              # Create features for each file
              files = manifest.get("files", [])

              if not files:
                  self.log("No files in manifest", fmeobjects.FME_WARN)
                  self.features_to_output.append(self._create_error_feature("No files downloaded"))
                  return

              self.log(f"Creating {len(files)} features from manifest...")

              for file_info in files:
                  feat = fmeobjects.FMEFeature()

                  # char(200) attributes
                  feat.setAttribute("record_number", str(file_info.get("record_number") or ""))
                  feat.setAttribute("title", str(file_info.get("title") or ""))
                  feat.setAttribute("filename", str(file_info.get("filename") or ""))
                  feat.setAttribute("filepath", str(file_info.get("filepath") or ""))
                  feat.setAttribute("source_record", str(manifest.get("record_number") or ""))
                  feat.setAttribute("download_timestamp", str(manifest.get("timestamp") or ""))
                  feat.setAttribute("error_message", str(file_info.get("error") or ""))

                  # logical attribute
                  feat.setAttribute("success", 1 if file_info.get("success") else 0)

                  # int32 attributes
                  feat.setAttribute("total_files", int(manifest.get("total_files") or 0))
                  feat.setAttribute("downloaded_count", int(manifest.get("downloaded") or 0))
                  feat.setAttribute("failed_count", int(manifest.get("failed") or 0))

                  # Status
                  feat.setAttribute("download_status", "SUCCESS" if file_info.get("success") else "FAILED")

                  self.features_to_output.append(feat)

              self.log(f"Successfully created {len(files)} features")
              self.log("=" * 60)

          def close(self):
              """
              Called after input() completes.
              Output all stored features using pyoutput.
              """
              for feat in self.features_to_output:
                  self.pyoutput(feat)

          def _create_error_feature(self, error_message):
              """Create an error feature"""
              feat = fmeobjects.FMEFeature()
              feat.setAttribute("record_number", "")
              feat.setAttribute("title", "")
              feat.setAttribute("filename", "")
              feat.setAttribute("filepath", "")
              feat.setAttribute("source_record", "")
              feat.setAttribute("download_timestamp", "")
              feat.setAttribute("error_message", str(error_message)[:200])
              feat.setAttribute("success", 0)
              feat.setAttribute("total_files", 0)
              feat.setAttribute("downloaded_count", 0)
              feat.setAttribute("failed_count", 0)
              feat.setAttribute("download_status", "ERROR")
              return feat
    PYTHONSYMBOL = FeatureCreator
    -> Tester
Note: filtering excel files
Tester
    BOOL_OP = COMPOSITE
    COMPOSITE_TEST = 1 AND 2 OR 3
    TEST_CLAUSE:
      TEST @Value(success) = 1
      CASE_INSENSITIVE_TEST @Value(filename) ENDS_WITH .xlsx
      CASE_INSENSITIVE_TEST @Value(filename) ENDS_WITH .xls
    TEST_MODE = TEST
    PASSED -> Tester_2
    PASSED -> Tester_3
Note: 5 year renewal
Tester_3
    BOOL_OP = OR
    TEST_CLAUSE:
      TEST @Value(title) = Parks Renewal Program - 5 years - 2025-26 to 2029-30
      TEST @Value(title) = Irrigation Renewal Program - 5 years - 2025-26 to 2029-30
      TEST @Value(title) = Sports Infrastructure Renewal Program - 5 years - 2025-26 to 2029-30
      TEST @Value(title) = Playground and Border Renewal Program - 4 Years - 2025-26 to 2028-29
      TEST @Value(title) = Wetlands and Native Open Space Renewal Program - 5 years - 2025-26 to 2029-30
      TEST @Value(title) = Guard Railing on Major Culverts Renewal Program - 5 years - 2025-26 to 2029-30
      TEST @Value(title) = Guard Railing on Road Bridges Renewal Program - 5 years - 2025-26 to 2029-30
      TEST @Value(title) = Dust Suppressant Seals Renewal Program - 5 years - 2025-26 to 2029-30
      TEST @Value(title) = Outdoor Furniture Renewal Program - 5 years - 2025-26 to 2029-30
    TEST_MODE = TEST
Note: 10 years renewal
Tester_2
    BOOL_OP = OR
    TEST_CLAUSE:
      TEST @Value(title) = Gravel Road Re-Sheeting Renewal Program - 10 years - 2026-27 to 2035-36
      TEST @Value(title) = Sealed Road Renewal Program - 10 Years - 2026-27 to 2035-36
      TEST @Value(title) = Kerb and Channel Renewal Program - 10 Years - 2026-27 to 2035-36
      TEST @Value(title) = Sealed Footpath Renewal Program - 10 Years - 2026-27 to 2035-36
      TEST @Value(title) = Shepparton Saleyards - 10 Years - 2024-2034
      TEST @Value(title) = Traffic Island Renewal Program - 10 Years - 2026-27 to 2035-36
      TEST @Value(title) = Bus Shelter Renewal Program - 10 Years - 2025/26 to 2034/35
      TEST @Value(title) = Shared Path Renewal Program - 10 years - 2025-26 to 2034-35
      TEST @Value(title) = Gravel Path Renewal Program - 10 years - 2025-26 to 2034-35
    TEST_MODE = TEST

Bookmark: Gravel Path Renewal Program - 10 years - 2025-26 to 2034-35
Gravel Path Renewal Program (reader XLSXR_1)
    attributes: Year number(2,0), Financial Year char(7), Unique Asset ID char(12), Asset ID combined char(181), Site Name char(40), Site ID char(7), Asset Class char(18), Location char(15), Area (sq m) number(9,4), Length (m) number(7,2), Width (m) number(4,2), Surface Type char(13), Maintenance Zone number(3,0), 2024 Condition number(1,0), Condition Notes char(20), Footpath Score char(8), Unit Rate number(2,0), Estimated Cost number(10,3), S char(46), T time
    -> PythonCaller
Program Summary (reader XLSXR_1)
    attributes: Year char(11), Financial Year char(7), Number Sites number(3,0), Total Area (sq m) number(10,4), Total Length (m) number(8,2), Total Estimated Cost number(11,3), Capital Budget number(8,1)

Bookmark: 10 year renewal data extracted from "E:\Administration\Projects\SP 2048 Automating content manger data for renewal programs\custom_search\download_test"
Note: spiliting the asset id combined
PythonCaller
    NEW_ATTRIBUTES = 2024 Condition uint8 Area (sq m) real32 Asset Class varchar(18) Asset ID combined varchar(181) Condition Notes varchar(20) Estimated Cost real64 Financial Year varchar(7) Footpath Score varchar(8) Length (m) real32 Location varchar(15) Maintenance Zone uint8 multi_reader_full_id uint8 multi_reader_id uint8 multi_reader_keyword varchar(7) multi_reader_type varchar(5) S varchar(46) Site ID varchar(7) Site Name varchar(40) Surface Type varchar(13) T real32 Unique Asset ID varchar(12) Unit Rate uint8 Width (m) real32 xlsx_row_id uint8 xlsx_type varchar(9) Year uint8
    PYTHONSOURCE:
      """
      FME PythonCaller: Asset ID Splitter

      This transformer splits rows with multiple Asset IDs (comma-separated)
      into individual rows for 1:1 spatial joins.

      Usage in FME:
      1. Add PythonCaller after FeatureReader (Excel)
      2. Set "Class to Process Features" to: AssetIDSplitter
      3. Expose the "Asset_ID" attribute in output

      Input: Features with "Asset ID combined" or similar column containing
             comma-separated IDs like "FP2637/0/24,FP2637/1/24"

      Output: Multiple features, one per Asset ID, with new "Asset_ID" attribute
              containing a single ID for spatial matching.
      """

      import fme
      from fme import BaseTransformer
      import fmeobjects


      class AssetIDSplitter(BaseTransformer):
          """
          Splits multi-ID values into separate features for 1:1 spatial joins.

          Looks for Asset ID columns and splits comma-separated values into
          individual features, duplicating all other attributes.
          """

          def __init__(self):
              """Initialize the transformer."""
              # Columns to check for Asset IDs (in order of preference)
              self.asset_id_columns = [
                  'Asset ID combined',
                  'Asset ID Combined',
                  'Asset_ID_combined',
                  'Asset ID',
                  'Asset_ID',
                  'Unique Asset ID',
                  'feature_id',
                  'Feature_ID',
              ]

              # Separators to check
              self.separators = [',', ';']

              # Statistics
              self.input_count = 0
              self.output_count = 0
              self.split_count = 0

          def has_support_for(self, support_type: int):
              """Enable bulk mode for performance."""
              return support_type == fmeobjects.FME_SUPPORT_FEATURE_TABLE_SHIM

          def find_asset_id_column(self, feature: fmeobjects.FMEFeature) -> str:
              """Find which Asset ID column exists in this feature."""
              all_attrs = feature.getAllAttributeNames()

              # Check our preferred columns first
              for col in self.asset_id_columns:
                  if col in all_attrs:
                      return col

              # Fallback: look for any column with 'asset' and 'id' in the name
              for attr in all_attrs:
                  attr_lower = attr.lower()
                  if 'asset' in attr_lower and 'id' in attr_lower:
                      if 'class' not in attr_lower:  # Exclude "Asset Class"
                          return attr

              return None

          def split_ids(self, value: str) -> list:
              """Split a multi-ID value into individual IDs."""
              if value is None:
                  return [None]

              value_str = str(value).strip()

              if not value_str:
                  return [None]

              # Try each separator
              for sep in self.separators:
                  if sep in value_str:
                      ids = [id.strip() for id in value_str.split(sep) if id.strip()]
                      if ids:
                          return ids

              # No separator found, return as single value
              return [value_str]

          def input(self, feature: fmeobjects.FMEFeature):
              """Process each input feature - split if multi-ID."""
              self.input_count += 1

              # Find the Asset ID column
              id_column = self.find_asset_id_column(feature)

              if id_column is None:
                  # No Asset ID column found - pass through unchanged
                  # But add empty Asset_ID for consistency
                  feature.setAttribute('Asset_ID', '')
                  self.pyoutput(feature, output_tag="PYOUTPUT")
                  self.output_count += 1
                  return

              # Get the value
              id_value = feature.getAttribute(id_column)

              # Split into individual IDs
              individual_ids = self.split_ids(id_value)

              if len(individual_ids) <= 1:
                  # Single ID or empty - output as-is with standardized column
                  single_id = individual_ids[0] if individual_ids else None
                  feature.setAttribute('Asset_ID', single_id if single_id else '')
                  self.pyoutput(feature, output_tag="PYOUTPUT")
                  self.output_count += 1
              else:
                  # Multiple IDs - create one feature per ID
                  self.split_count += 1

                  for asset_id in individual_ids:
                      # Clone the feature (copies all attributes and geometry)
                      new_feature = feature.clone()

                      # Set the standardized Asset_ID to this single ID
                      new_feature.setAttribute('Asset_ID', asset_id)

                      # Also update the original column to single value
                      new_feature.setAttribute(id_column, asset_id)

                      self.pyoutput(new_feature, output_tag="PYOUTPUT")
                      self.output_count += 1

          def close(self):
              """Log statistics when processing completes."""
              logger = fmeobjects.FMELogFile()
              logger.logMessageString("=" * 60, fmeobjects.FME_INFORM)
              logger.logMessageString("Asset ID Splitter Summary:", fmeobjects.FME_INFORM)
              logger.logMessageString(f"  Input features: {self.input_count}", fmeobjects.FME_INFORM)
              logger.logMessageString(f"  Output features: {self.output_count}", fmeobjects.FME_INFORM)
              logger.logMessageString(f"  Features split: {self.split_count}", fmeobjects.FME_INFORM)
              logger.logMessageString(f"  Features added: {self.output_count - self.input_count}", fmeobjects.FME_INFORM)
              logger.logMessageString("=" * 60, fmeobjects.FME_INFORM)

          def process_group(self):
              """Called for each group when group processing mode is enabled."""
              pass

          def reject_feature(self, feature: fmeobjects.FMEFeature, code: str, message: str):
              """Output a feature to the <Rejected> port."""
              feature.setAttribute("fme_rejection_code", code)
              feature.setAttribute("fme_rejection_message", message)
              self.pyoutput(feature, output_tag="<Rejected>")


      # For backwards compatibility, also expose as FeatureProcessor
      FeatureProcessor = AssetIDSplitter
    PYTHONSYMBOL = FeatureProcessor
PythonCaller_2
    NEW_ATTRIBUTES = 2024 Condition uint8 Area (sq m) real32 Asset Class varchar(18) Asset ID combined varchar(181) Condition Notes varchar(20) Estimated Cost real64 Financial Year varchar(7) Footpath Score varchar(8) Length (m) real32 Location varchar(15) Maintenance Zone uint8 multi_reader_full_id uint8 multi_reader_id uint8 multi_reader_keyword varchar(7) multi_reader_type varchar(5) S varchar(46) Site ID varchar(7) Site Name varchar(40) Surface Type varchar(13) T real32 Unique Asset ID varchar(12) Unit Rate uint8 Width (m) real32 xlsx_row_id uint8 xlsx_type varchar(9) Year uint8 2024 Condition uint8 Area (sq m) real32 Asset ID combined varchar(431) Condition Notes varchar(65) Estimated Cost real64 Financial Year varchar(7) Length (m) real32 P varchar(41) Site ID varchar(7) Site Name varchar(40) Surface Type varchar(10) Unique Asset ID varchar(12) Unit Rate uint8 Width (m) real32
    PYTHONSOURCE:
      """
      FME PythonCaller: Asset ID Splitter

      This transformer splits rows with multiple Asset IDs (comma-separated)
      into individual rows for 1:1 spatial joins.

      Usage in FME:
      1. Add PythonCaller after FeatureReader (Excel)
      2. Set "Class to Process Features" to: AssetIDSplitter
      3. Expose the "Asset_ID" attribute in output

      Input: Features with "Asset ID combined" or similar column containing
             comma-separated IDs like "FP2637/0/24,FP2637/1/24"

      Output: Multiple features, one per Asset ID, with new "Asset_ID" attribute
              containing a single ID for spatial matching.
      """

      import fme
      from fme import BaseTransformer
      import fmeobjects


      class AssetIDSplitter(BaseTransformer):
          """
          Splits multi-ID values into separate features for 1:1 spatial joins.

          Looks for Asset ID columns and splits comma-separated values into
          individual features, duplicating all other attributes.
          """

          def __init__(self):
              """Initialize the transformer."""
              # Columns to check for Asset IDs (in order of preference)
              self.asset_id_columns = [
                  'Asset ID combined',
                  'Asset ID Combined',
                  'Asset_ID_combined',
                  'Asset ID',
                  'Asset_ID',
                  'Unique Asset ID',
                  'feature_id',
                  'Feature_ID',
              ]

              # Separators to check
              self.separators = [',', ';']

              # Statistics
              self.input_count = 0
              self.output_count = 0
              self.split_count = 0

          def has_support_for(self, support_type: int):
              """Enable bulk mode for performance."""
              return support_type == fmeobjects.FME_SUPPORT_FEATURE_TABLE_SHIM

          def find_asset_id_column(self, feature: fmeobjects.FMEFeature) -> str:
              """Find which Asset ID column exists in this feature."""
              all_attrs = feature.getAllAttributeNames()

              # Check our preferred columns first
              for col in self.asset_id_columns:
                  if col in all_attrs:
                      return col

              # Fallback: look for any column with 'asset' and 'id' in the name
              for attr in all_attrs:
                  attr_lower = attr.lower()
                  if 'asset' in attr_lower and 'id' in attr_lower:
                      if 'class' not in attr_lower:  # Exclude "Asset Class"
                          return attr

              return None

          def split_ids(self, value: str) -> list:
              """Split a multi-ID value into individual IDs."""
              if value is None:
                  return [None]

              value_str = str(value).strip()

              if not value_str:
                  return [None]

              # Try each separator
              for sep in self.separators:
                  if sep in value_str:
                      ids = [id.strip() for id in value_str.split(sep) if id.strip()]
                      if ids:
                          return ids

              # No separator found, return as single value
              return [value_str]

          def input(self, feature: fmeobjects.FMEFeature):
              """Process each input feature - split if multi-ID."""
              self.input_count += 1

              # Find the Asset ID column
              id_column = self.find_asset_id_column(feature)

              if id_column is None:
                  # No Asset ID column found - pass through unchanged
                  # But add empty Asset_ID for consistency
                  feature.setAttribute('Asset_ID', '')
                  self.pyoutput(feature, output_tag="PYOUTPUT")
                  self.output_count += 1
                  return

              # Get the value
              id_value = feature.getAttribute(id_column)

              # Split into individual IDs
              individual_ids = self.split_ids(id_value)

              if len(individual_ids) <= 1:
                  # Single ID or empty - output as-is with standardized column
                  single_id = individual_ids[0] if individual_ids else None
                  feature.setAttribute('Asset_ID', single_id if single_id else '')
                  self.pyoutput(feature, output_tag="PYOUTPUT")
                  self.output_count += 1
              else:
                  # Multiple IDs - create one feature per ID
                  self.split_count += 1

                  for asset_id in individual_ids:
                      # Clone the feature (copies all attributes and geometry)
                      new_feature = feature.clone()

                      # Set the standardized Asset_ID to this single ID
                      new_feature.setAttribute('Asset_ID', asset_id)

                      # Also update the original column to single value
                      new_feature.setAttribute(id_column, asset_id)

                      self.pyoutput(new_feature, output_tag="PYOUTPUT")
                      self.output_count += 1

          def close(self):
              """Log statistics when processing completes."""
              logger = fmeobjects.FMELogFile()
              logger.logMessageString("=" * 60, fmeobjects.FME_INFORM)
              logger.logMessageString("Asset ID Splitter Summary:", fmeobjects.FME_INFORM)
              logger.logMessageString(f"  Input features: {self.input_count}", fmeobjects.FME_INFORM)
              logger.logMessageString(f"  Output features: {self.output_count}", fmeobjects.FME_INFORM)
              logger.logMessageString(f"  Features split: {self.split_count}", fmeobjects.FME_INFORM)
              logger.logMessageString(f"  Features added: {self.output_count - self.input_count}", fmeobjects.FME_INFORM)
              logger.logMessageString("=" * 60, fmeobjects.FME_INFORM)

          def process_group(self):
              """Called for each group when group processing mode is enabled."""
              pass

          def reject_feature(self, feature: fmeobjects.FMEFeature, code: str, message: str):
              """Output a feature to the <Rejected> port."""
              feature.setAttribute("fme_rejection_code", code)
              feature.setAttribute("fme_rejection_message", message)
              self.pyoutput(feature, output_tag="<Rejected>")


      # For backwards compatibility, also expose as FeatureProcessor
      FeatureProcessor = AssetIDSplitter
    PYTHONSYMBOL = FeatureProcessor
PythonCaller_3
    NEW_ATTRIBUTES = 2024 Condition uint8 Area (sq m) real32 Asset Class varchar(18) Asset ID combined varchar(181) Condition Notes varchar(20) Estimated Cost real64 Financial Year varchar(7) Footpath Score varchar(8) Length (m) real32 Location varchar(15) Maintenance Zone uint8 multi_reader_full_id uint8 multi_reader_id uint8 multi_reader_keyword varchar(7) multi_reader_type varchar(5) S varchar(46) Site ID varchar(7) Site Name varchar(40) Surface Type varchar(13) T real32 Unique Asset ID varchar(12) Unit Rate uint8 Width (m) real32 xlsx_row_id uint8 xlsx_type varchar(9) Year uint8 AB real64 Area m2 real32 Area m200 real32 Asset Class varchar(15) Asset ID varchar(13) Asset ID Combined varchar(95) Comments varchar(123) Condition 2024 uint8 Design Completed varchar(3) Detailed Assessment Comments varchar(47) Estimated Cost real64 Estimated Cost00 uint32 Financial Year varchar(7) Footpath Score uint8 Footpath Type varchar(15) Length m real32 Length m00 uint8 Priority varchar(4) Renewal Width real32 Renewal Width00 real32 Site Code varchar(7) Site_Name varchar(40) Unit Rate uint16 Unit Rate00 uint16 Width m real32 Width m00 real32
    PYTHONSOURCE:
      """
      FME PythonCaller: Asset ID Splitter

      This transformer splits rows with multiple Asset IDs (comma-separated)
      into individual rows for 1:1 spatial joins.

      Usage in FME:
      1. Add PythonCaller after FeatureReader (Excel)
      2. Set "Class to Process Features" to: AssetIDSplitter
      3. Expose the "Asset_ID" attribute in output

      Input: Features with "Asset ID combined" or similar column containing
             comma-separated IDs like "FP2637/0/24,FP2637/1/24"

      Output: Multiple features, one per Asset ID, with new "Asset_ID" attribute
              containing a single ID for spatial matching.
      """

      import fme
      from fme import BaseTransformer
      import fmeobjects


      class AssetIDSplitter(BaseTransformer):
          """
          Splits multi-ID values into separate features for 1:1 spatial joins.

          Looks for Asset ID columns and splits comma-separated values into
          individual features, duplicating all other attributes.
          """

          def __init__(self):
              """Initialize the transformer."""
              # Columns to check for Asset IDs (in order of preference)
              self.asset_id_columns = [
                  'Asset ID combined',
                  'Asset ID Combined',
                  'Asset_ID_combined',
                  'Asset ID',
                  'Asset_ID',
                  'Unique Asset ID',
                  'feature_id',
                  'Feature_ID',
              ]

              # Separators to check
              self.separators = [',', ';']

              # Statistics
              self.input_count = 0
              self.output_count = 0
              self.split_count = 0

          def has_support_for(self, support_type: int):
              """Enable bulk mode for performance."""
              return support_type == fmeobjects.FME_SUPPORT_FEATURE_TABLE_SHIM

          def find_asset_id_column(self, feature: fmeobjects.FMEFeature) -> str:
              """Find which Asset ID column exists in this feature."""
              all_attrs = feature.getAllAttributeNames()

              # Check our preferred columns first
              for col in self.asset_id_columns:
                  if col in all_attrs:
                      return col

              # Fallback: look for any column with 'asset' and 'id' in the name
              for attr in all_attrs:
                  attr_lower = attr.lower()
                  if 'asset' in attr_lower and 'id' in attr_lower:
                      if 'class' not in attr_lower:  # Exclude "Asset Class"
                          return attr

              return None

          def split_ids(self, value: str) -> list:
              """Split a multi-ID value into individual IDs."""
              if value is None:
                  return [None]

              value_str = str(value).strip()

              if not value_str:
                  return [None]

              # Try each separator
              for sep in self.separators:
                  if sep in value_str:
                      ids = [id.strip() for id in value_str.split(sep) if id.strip()]
                      if ids:
                          return ids

              # No separator found, return as single value
              return [value_str]

          def input(self, feature: fmeobjects.FMEFeature):
              """Process each input feature - split if multi-ID."""
              self.input_count += 1

              # Find the Asset ID column
              id_column = self.find_asset_id_column(feature)

              if id_column is None:
                  # No Asset ID column found - pass through unchanged
                  # But add empty Asset_ID for consistency
                  feature.setAttribute('Asset_ID', '')
                  self.pyoutput(feature, output_tag="PYOUTPUT")
                  self.output_count += 1
                  return

              # Get the value
              id_value = feature.getAttribute(id_column)

              # Split into individual IDs
              individual_ids = self.split_ids(id_value)

              if len(individual_ids) <= 1:
                  # Single ID or empty - output as-is with standardized column
                  single_id = individual_ids[0] if individual_ids else None
                  feature.setAttribute('Asset_ID', single_id if single_id else '')
                  self.pyoutput(feature, output_tag="PYOUTPUT")
                  self.output_count += 1
              else:
                  # Multiple IDs - create one feature per ID
                  self.split_count += 1

                  for asset_id in individual_ids:
                      # Clone the feature (copies all attributes and geometry)
                      new_feature = feature.clone()

                      # Set the standardized Asset_ID to this single ID
                      new_feature.setAttribute('Asset_ID', asset_id)

                      # Also update the original column to single value
                      new_feature.setAttribute(id_column, asset_id)

                      self.pyoutput(new_feature, output_tag="PYOUTPUT")
                      self.output_count += 1

          def close(self):
              """Log statistics when processing completes."""
              logger = fmeobjects.FMELogFile()
              logger.logMessageString("=" * 60, fmeobjects.FME_INFORM)
              logger.logMessageString("Asset ID Splitter Summary:", fmeobjects.FME_INFORM)
              logger.logMessageString(f"  Input features: {self.input_count}", fmeobjects.FME_INFORM)
              logger.logMessageString(f"  Output features: {self.output_count}", fmeobjects.FME_INFORM)
              logger.logMessageString(f"  Features split: {self.split_count}", fmeobjects.FME_INFORM)
              logger.logMessageString(f"  Features added: {self.output_count - self.input_count}", fmeobjects.FME_INFORM)
              logger.logMessageString("=" * 60, fmeobjects.FME_INFORM)

          def process_group(self):
              """Called for each group when group processing mode is enabled."""
              pass

          def reject_feature(self, feature: fmeobjects.FMEFeature, code: str, message: str):
              """Output a feature to the <Rejected> port."""
              feature.setAttribute("fme_rejection_code", code)
              feature.setAttribute("fme_rejection_message", message)
              self.pyoutput(feature, output_tag="<Rejected>")


      # For backwards compatibility, also expose as FeatureProcessor
      FeatureProcessor = AssetIDSplitter
    PYTHONSYMBOL = FeatureProcessor
PythonCaller_4
    NEW_ATTRIBUTES = 2024 Condition uint8 Area (sq m) real32 Asset Class varchar(18) Asset ID combined varchar(181) Condition Notes varchar(20) Estimated Cost real64 Financial Year varchar(7) Footpath Score varchar(8) Length (m) real32 Location varchar(15) Maintenance Zone uint8 multi_reader_full_id uint8 multi_reader_id uint8 multi_reader_keyword varchar(7) multi_reader_type varchar(5) S varchar(46) Site ID varchar(7) Site Name varchar(40) Surface Type varchar(13) T real32 Unique Asset ID varchar(12) Unit Rate uint8 Width (m) real32 xlsx_row_id uint8 xlsx_type varchar(9) Year uint8 AB real64 Area m2 real32 Area m200 real32 Asset Class varchar(15) Asset ID varchar(13) Asset ID Combined varchar(95) Comments varchar(123) Condition 2024 uint8 Design Completed varchar(3) Detailed Assessment Comments varchar(47) Estimated Cost real64 Estimated Cost00 uint32 Financial Year varchar(7) Footpath Score uint8 Footpath Type varchar(15) Length m real32 Length m00 uint8 Priority varchar(4) Renewal Width real32 Renewal Width00 real32 Site Code varchar(7) Site_Name varchar(40) Unit Rate uint16 Unit Rate00 uint16 Width m real32 Width m00 real32 2024 Condition uint8 Asset ID varchar(14) Asset ID00 varchar(35) Comment varchar(159) Design Completed varchar(3) Estimated Cost real64 Estimated Cost00 real64 Financial Year varchar(7) Kerb and Channel Type varchar(8) Length m real32 Length m00 uint16 Network Measure real32 Network Measure00 uint16 Site Code varchar(7) Unit Rate uint16 Unit Rate00 uint16 Width m uint16 Width mm uint16
    PYTHONSOURCE:
      """
      FME PythonCaller: Asset ID Splitter

      This transformer splits rows with multiple Asset IDs (comma-separated)
      into individual rows for 1:1 spatial joins.

      Usage in FME:
      1. Add PythonCaller after FeatureReader (Excel)
      2. Set "Class to Process Features" to: AssetIDSplitter
      3. Expose the "Asset_ID" attribute in output

      Input: Features with "Asset ID combined" or similar column containing
             comma-separated IDs like "FP2637/0/24,FP2637/1/24"

      Output: Multiple features, one per Asset ID, with new "Asset_ID" attribute
              containing a single ID for spatial matching.
      """

      import fme
      from fme import BaseTransformer
      import fmeobjects


      class AssetIDSplitter(BaseTransformer):
          """
          Splits multi-ID values into separate features for 1:1 spatial joins.

          Looks for Asset ID columns and splits comma-separated values into
          individual features, duplicating all other attributes.
          """

          def __init__(self):
              """Initialize the transformer."""
              # Columns to check for Asset IDs (in order of preference)
              self.asset_id_columns = [
                  'Asset ID combined',
                  'Asset ID Combined',
                  'Asset_ID_combined',
                  'Asset ID00',
                  'Asset ID',
                  'Asset_ID',
                  'Unique Asset ID',
                  'feature_id',
                  'Feature_ID',
              ]

              # Separators to check
              self.separators = [',', ';']

              # Statistics
              self.input_count = 0
              self.output_count = 0
              self.split_count = 0

          def has_support_for(self, support_type: int):
              """Enable bulk mode for performance."""
              return support_type == fmeobjects.FME_SUPPORT_FEATURE_TABLE_SHIM

          def find_asset_id_column(self, feature: fmeobjects.FMEFeature) -> str:
              """Find which Asset ID column exists in this feature."""
              all_attrs = feature.getAllAttributeNames()

              # Check our preferred columns first
              for col in self.asset_id_columns:
                  if col in all_attrs:
                      return col

              # Fallback: look for any column with 'asset' and 'id' in the name
              for attr in all_attrs:
                  attr_lower = attr.lower()
                  if 'asset' in attr_lower and 'id' in attr_lower:
                      if 'class' not in attr_lower:  # Exclude "Asset Class"
                          return attr

              return None

          def split_ids(self, value: str) -> list:
              """Split a multi-ID value into individual IDs."""
              if value is None:
                  return [None]

              value_str = str(value).strip()

              if not value_str:
                  return [None]

              # Try each separator
              for sep in self.separators:
                  if sep in value_str:
                      ids = [id.strip() for id in value_str.split(sep) if id.strip()]
                      if ids:
                          return ids

              # No separator found, return as single value
              return [value_str]

          def input(self, feature: fmeobjects.FMEFeature):
              """Process each input feature - split if multi-ID."""
              self.input_count += 1

              # Find the Asset ID column
              id_column = self.find_asset_id_column(feature)

              if id_column is None:
                  # No Asset ID column found - pass through unchanged
                  # But add empty Asset_ID for consistency
                  feature.setAttribute('Asset_ID', '')
                  self.pyoutput(feature, output_tag="PYOUTPUT")
                  self.output_count += 1
                  return

              # Get the value
              id_value = feature.getAttribute(id_column)

              # Split into individual IDs
              individual_ids = self.split_ids(id_value)

              if len(individual_ids) <= 1:
                  # Single ID or empty - output as-is with standardized column
                  single_id = individual_ids[0] if individual_ids else None
                  feature.setAttribute('Asset_ID', single_id if single_id else '')
                  self.pyoutput(feature, output_tag="PYOUTPUT")
                  self.output_count += 1
              else:
                  # Multiple IDs - create one feature per ID
                  self.split_count += 1

                  for asset_id in individual_ids:
                      # Clone the feature (copies all attributes and geometry)
                      new_feature = feature.clone()

                      # Set the standardized Asset_ID to this single ID
                      new_feature.setAttribute('Asset_ID', asset_id)

                      # Also update the original column to single value
                      new_feature.setAttribute(id_column, asset_id)

                      self.pyoutput(new_feature, output_tag="PYOUTPUT")
                      self.output_count += 1

          def close(self):
              """Log statistics when processing completes."""
              logger = fmeobjects.FMELogFile()
              logger.logMessageString("=" * 60, fmeobjects.FME_INFORM)
              logger.logMessageString("Asset ID Splitter Summary:", fmeobjects.FME_INFORM)
              logger.logMessageString(f"  Input features: {self.input_count}", fmeobjects.FME_INFORM)
              logger.logMessageString(f"  Output features: {self.output_count}", fmeobjects.FME_INFORM)
              logger.logMessageString(f"  Features split: {self.split_count}", fmeobjects.FME_INFORM)
              logger.logMessageString(f"  Features added: {self.output_count - self.input_count}", fmeobjects.FME_INFORM)
              logger.logMessageString("=" * 60, fmeobjects.FME_INFORM)

          def process_group(self):
              """Called for each group when group processing mode is enabled."""
              pass

          def reject_feature(self, feature: fmeobjects.FMEFeature, code: str, message: str):
              """Output a feature to the <Rejected> port."""
              feature.setAttribute("fme_rejection_code", code)
              feature.setAttribute("fme_rejection_message", message)
              self.pyoutput(feature, output_tag="<Rejected>")


      # For backwards compatibility, also expose as FeatureProcessor
      FeatureProcessor = AssetIDSplitter
    PYTHONSYMBOL = FeatureProcessor

Bookmark: Shared Path Renewal Program - 10 years - 2025-26 to 2034-35
Shared Path Renewal Program (reader XLSXR_11)
    attributes: Year number(2,0), Financial Year char(7), Unique Asset ID char(12), Asset ID combined char(431), Site Name char(40), Site ID char(7), Location char(13), Area (sq m) number(8,3), Length (m) number(7,2), Width (m) number(3,1), Surface Type char(10), 2024 Condition number(1,0), Condition Notes char(65), Unit Rate number(3,0), Estimated Cost number(9,2), P char(41)
    -> PythonCaller_2
Sheet1 (reader XLSXR_10)
    attributes: Year char(11), Financial Year char(7), Sum of Estimated Cost number(10,2), LTFP Funding time, E number(18,11)

Bookmark: Bus Shelter Renewal Program - 10 Years - 2025/26 to 2034/35
Detailed (reader XLSXR_3)
    attributes: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
Summary (reader XLSXR_3)
    attributes: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

Bookmark: New Traffic Island Renewal Program - 10 Years - 2026-27 to 2035-36
Renewal Plan (reader XLSXR_2)
    attributes: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

Bookmark: Shepparton Saleyards - 10 Years - 2024-2034
Sheet1 (reader XLSXR_4)
    attributes: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

Bookmark: Sealed Footpath Renewal Program - 10 Years - 2026-27 to 2035-36
Deleted (reader XLSXR_6)
    attributes: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
Renewal Program 2026-2036 (reader XLSXR_5)
    attributes: Year number(2,0), Financial Year char(7), Asset ID char(13), Asset ID Combined char(95), Site_Name char(40), Site Code char(7), Asset Class char(15), Location char(14), Length m number(6,2), Width m number(5,2), Renewal Width number(5,2), Area m2 number(9,4), Condition 2024 number(1,0), Footpath Score number(2,0), Footpath Type char(15), Unit Rate number(3,0), Estimated Cost number(12,3), Comments char(123), Priority char(4), Design Completed boolean, Detailed Assessment Comments char(47), Length m00 number(3,0), Width m00 number(3,1), Renewal Width00 number(4,2), Area m200 number(6,2), Unit Rate00 number(3,0), Estimated Cost00 number(6,0), AB number(7,1)
    -> PythonCaller_3

Bookmark: Kerb and Channel Renewal Program - 10 Years - 2026-27 to 2035-36
Deleted (reader XLSXR_7)
    attributes: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
Kerb and Channel Renewal Progra (reader XLSXR_12)
    attributes: Year number(2,0), Financial Year char(7), Asset ID char(14), Asset ID00 char(35), Site_Name char(39), Site Code char(7), Location char(14), Length m number(6,2), Width mm number(3,0), Network Measure number(6,2), 2024 Condition number(1,0), Unit Rate number(3,0), Estimated Cost number(10,1), Kerb and Channel Type char(8), Comments string, Priority char(4), Comment char(159), Length m00 number(3,0), Width m number(3,0), Network Measure00 number(3,0), Unit Rate00 number(3,0), Estimated Cost00 number(9,2), Design Completed boolean
    -> PythonCaller_4

Bookmark: Sealed Road Renewal Program - 10 Years - 2026-27 to 2035-36
Removed from program (reader XLSXR_8)
    attributes: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
Sealed Roads (reader XLSXR_13)
    attributes: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
Unit Rates (reader XLSXR_8)
    attributes: Treatment Name char(40), Unit Cost (m2) number(5,1)
Year 1 - 2026-27 (reader XLSXR_13)
    attributes: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

Bookmark: Gravel Road Re-Sheeting Renewal Program - 10 years - 2026-27 to 2035-36
Gravel Re-sheet Renewal Program (reader XLSXR_14)
    attributes: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
Year 1 - 2026-27 (reader XLSXR_14)
    attributes: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
Sheet1 (reader XLSXR_9)
    attributes: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
